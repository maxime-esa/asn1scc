-- It tests the   
-- 'pdu1' does conform to its type constraints. 

TEST-CASE DEFINITIONS AUTOMATIC TAGS::= BEGIN
    
    MyPDU ::= SEQUENCE {
        tap     TAP3File
	}

    TAP3File::=SEQUENCE {
        header  HeaderType,
        data    SourceData
    }

    HeaderType::=SEQUENCE {
        operatorID  IA5String(SIZE(1..10))
    }
	CallsSize ::= INTEGER (1..10)
    
    SourceData::=SEQUENCE {
        
        calls   CallsArray
    }	

    CallsArray ::= SEQUENCE (SIZE(1..10)) OF Call
    
    Call ::= IA5String(SIZE(1..5))
    
	pdu1 MyPDU ::= { tap { 
	                    header{operatorID "FA23DF"}, 
	                    data{ calls{"22433","23423","57437","43632"} } 
	                 }
	               }
	
END

--TCFS     001_10.acn
