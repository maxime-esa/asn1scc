-- It tests the   
-- 'pdu1' does conform to its type constraints. 

TEST-CASE DEFINITIONS AUTOMATIC TAGS::= BEGIN
    
    MyPDU ::= SEQUENCE {
        primaryHeader HeaderType,
        secondaryHeader Payload OPTIONAL
	}
    
    HeaderType ::= SEQUENCE {
            version INTEGER,
            seqNr   INTEGER,
            secHeaderFlag   BOOLEAN
        }
    Payload ::= SEQUENCE { dummy INTEGER}
    
	pdu1 MyPDU ::= { 
	                primaryHeader { version 2, seqNr 21321, secHeaderFlag FALSE}
	               }
	
END

--TCFFC     001_02_1.acn	$$$ File:sample1.asn1, line:15, ASN.1 fields cannot act as encoding determinants. Remove field 'secHeaderFlag' from the ASN.1 grammar and introduce it in the ACN grammar
