TEST-CASE DEFINITIONS AUTOMATIC TAGS::= BEGIN

	MyPDU ::= IA5String(SIZE(1..20))
	
	pdu1 MyPDU ::= "George Mamais"
	
END


--TCLFC    MyPDU[size 20]               $$$ File:sample1.acn, line:4, The size constraints of the ASN.1  allows variable items (1 .. 20). Therefore, you should either remove the size property (in which case the size determinant will be encoded automatically exactly like uPER), or use a an Integer field as size determinant
--TCLS     MyPDU[]
-- TCLS     MyPDU[size null-terminated]
