TEST-CASE DEFINITIONS AUTOMATIC TAGS::= BEGIN

	MyPDU ::= IA5String(SIZE(20))(FROM("A".."Z"|"a".."z"|" "))
	pdu1 MyPDU ::= "George Mamais       "
	
END

-- ASCII encodings
--TCLS     MyPDU[encoding ASCII, size null-terminated, termination-pattern '00000001'B]
--TCLS     MyPDU[encoding ASCII, size 20]
--TCLS     MyPDU[encoding ASCII, size null-terminated]

-- char index encodings
--TCLS     MyPDU[]
--TCLS     MyPDU[size 20]
