TEST-CASE DEFINITIONS AUTOMATIC TAGS::= BEGIN

	MyPDU ::= OCTET STRING (SIZE(1..20))
	
	pdu1 MyPDU ::= 'AFBC4583'H
	
END


--TCLS     MyPDU[]
--TCLFC    MyPDU[size 20]               $$$ File:sample1.acn, line:4, The size constraints of the ASN.1  allows variable items (1 .. 20). Therefore, you should either remove the size property (in which case the size determinant will be encoded automatically exactly like uPER), or use a an Integer field as size determinant
--TCLFC    MyPDU[size null-terminated]   $$$ File:sample1.acn, line:4, Acn proporty 'size null-terminated' is supported only in IA5String and NumericString string types and in Integer types and when encoding is ASCII
