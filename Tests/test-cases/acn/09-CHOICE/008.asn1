TEST-CASE DEFINITIONS AUTOMATIC TAGS::= BEGIN


    MyPDU ::= SEQUENCE {
        a  MyPDU-a,
        b MySequence
    }
	
	MyPDU-a ::= SEQUENCE 
	{
		a1 INTEGER
		
    }	
    
	MySequence ::= SEQUENCE {
        b   ChoiceType
    }
    
    ChoiceSelector ::= ENUMERATED {
        int1, int2, enm, buf, gg
    }
    
    
    ChoiceType ::= CHOICE {
		int1	INTEGER(0..15),
		int2	INTEGER(0..65535),
		enm		ENUMERATED {
					one(1), two(2), three(3),
					 four(4), thousand(1000)
				},
		buf	 OCTET STRING (SIZE(10)),
		gg  SEQUENCE {
			int1	INTEGER(0..15),
			int2	INTEGER(0..65535),
			enm	ENUMERATED {
					pone(1), ptwo(2), pthree(3),
					 pfour(4), pthousand(1000)
				},
			buf	[APPLICATION 104]	OCTET STRING (SIZE(10))
		}
	}
	
	pdu1 MyPDU ::= {a {a1 20}, b {b gg : {int1 10, int2 200, enm pone, buf '00112233445566778899'H }}}

END

--TCLS     MyPDU-a[] {a1[], b ChoiceSelector[]} MyPDU[] {a[], b<a.b>[]}   ChoiceSelector[]  ChoiceType<ChoiceSelector:sel>[determinant sel] MySequence<ChoiceSelector:sel>[]{b<sel>[]}
