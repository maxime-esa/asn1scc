TEST-CASE DEFINITIONS AUTOMATIC TAGS::= BEGIN

	MyPDU ::= SEQUENCE {
        header   HeaderType,
        payload   ChoiceType
    }
    
    HeaderType ::= SEQUENCE {
        a1 INTEGER
        
    }
        
    ChoiceSelector ::= ENUMERATED {
        int1, int2, enm, buf, gg
    }
    
    
    ChoiceType ::= CHOICE {
		int1	INTEGER(0..15),
		int2	INTEGER(0..65535),
		enm		ENUMERATED {
					one(1), two(2), three(3),
					 four(4), thousand(1000)
				},
		buf	 OCTET STRING (SIZE(10)),
		gg  SEQUENCE {
			int1	INTEGER(0..15),
			int2	INTEGER(0..65535),
			enm	ENUMERATED {
					pone(1), ptwo(2), pthree(3),
					 pfour(4), pthousand(1000)
				},
			buf	[APPLICATION 104]	OCTET STRING (SIZE(10))
		}
	}
	
	pdu1 MyPDU ::= {header {a1 20}, payload gg : {int1 10, int2 200, enm pone, buf '00112233445566778899'H }}

END

--TCLS     MyPDU[] {header[], payload<header.chSelector>[]}   HeaderType[] {a1[], chSelector ChoiceSelector[]} ChoiceSelector[]  ChoiceType<ChoiceSelector:sel>[determinant sel]
