TEST-CASE  DEFINITIONS AUTOMATIC TAGS::= BEGIN

	MyPDU ::= SEQUENCE {
            a INTEGER,
            b NULL,
            c NumericString(SIZE(2))
	}
	
	pdu1 MyPDU ::= {a 1, b NULL, c "42"}
--TCLS     MyPDU[] {a[], b[], c[]}
--TCLFC    MyPDU[] {a[], b[]}  $$$ File:sample1.asn1, line:6, No ACN specification provided for 'c' component
	
END
