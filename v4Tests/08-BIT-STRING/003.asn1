TEST-CASE DEFINITIONS AUTOMATIC TAGS::= BEGIN

	MyPDU ::= SEQUENCE {
        a   INTEGER(16),
        b   BIT STRING (SIZE(16))
    }
	POS-INT ::= INTEGER(0..100)
	pdu1 MyPDU ::= {a 16, b'ABCD'H}
	
END

--TCLS    MyPDU[] {a[], b[size 16]}
--TCLS    MyPDU[]
--  TCLS    POS-INT[size 13, encoding pos-int] MyPDU[] {a[], insertedInAcn POS-INT[], b[size insertedInAcn, align-to-next word]}
