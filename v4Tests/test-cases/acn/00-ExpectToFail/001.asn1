TEST-CASE DEFINITIONS AUTOMATIC TAGS::= BEGIN

	MyPDU ::= MyPDU2
	
	MyPDU2 ::= SEQUENCE {
		a MyPDU OPTIONAL
	}
	
END

--TCLFC    MyPDU[encoding pos-int, size 6]          $$$ File:sample1.asn1, line:3, Cyclic dependencies detected : Type assignment 'TEST-CASE.MyPDU' depends on : 'TEST-CASE.MyPDU2' and Type assignment 'TEST-CASE.MyPDU2' depends on : 'TEST-CASE.MyPDU'
