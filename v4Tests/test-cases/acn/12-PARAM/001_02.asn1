-- It tests the   
-- 'pdu1' does conform to its type constraints. 

TEST-CASE DEFINITIONS AUTOMATIC TAGS::= BEGIN
    
    MyPDU ::= SEQUENCE {
        primaryHeader SEQUENCE {
            version INTEGER,
            seqNr   INTEGER,
            secHeaderFlag   BOOLEAN
        },
        secondaryHeader SEQUENCE { dummy INTEGER} OPTIONAL
	}

    
	pdu1 MyPDU ::= { 
	                primaryHeader { version 2, seqNr 21321, secHeaderFlag FALSE}
	               }
	
END

--TCFFC     001_02.acn  $$$ File:sample1.acn, line:10, ASN.1 fields cannot act as encoding determinants. Remove field 'secHeaderFlag' from the ASN.1 grammar and introduce it in the ACN grammar
