TEST-CASE DEFINITIONS AUTOMATIC TAGS::= BEGIN

	MyPDU ::= BIT STRING (SIZE(1..20))
	
	pdu1 MyPDU ::= 'ABCD'H
	
END

--TCLS     MyPDU[]
--TCLFC    MyPDU[size null-terminated]      $$$ File:sample1.acn, line:4, Acn proporty 'size null-terminated' is supported only in IA5String and NumericString string types and in Integer types and when encoding is ASCII
