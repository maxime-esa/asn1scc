TEST-CASE DEFINITIONS AUTOMATIC TAGS::= BEGIN

	MyPDU ::= SEQUENCE {
       a2 IA5String(SIZE(20))
    }
	
	AT1 ::= INTEGER (1..100)
	
	pdu1 MyPDU ::= {a2 "George Mamais       "}
	
END

-- ASCII encodings
--TCLS     MyPDU[] { a1 AT1[], a2[size a1, encoding ASCII]} 
-- char index encodings
--TCLS     MyPDU[] { a1 AT1[], a2[size a1]}
