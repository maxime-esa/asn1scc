TEST-CASE DEFINITIONS AUTOMATIC TAGS::= BEGIN

	MyPDU ::= SEQUENCE {
       a1 INTEGER,
       a2 IA5String(SIZE(20))(FROM("A".."Z"|"a".."z"|" "))
    }
	
	pdu1 MyPDU ::= {a1 20, a2 "George Mamais       "}
	
END

--TCLS     MyPDU[]
--TCLS     MyPDU[] { a1[], a2[]}
-- TCLS     MyPDU[] { a1[], a2[size null-terminated]}
--TCLS    MyPDU[] { a1[], a2[size 20]}               
--TCLFC    MyPDU[] { a1[], a2[size 25]}               $$$ File:sample1.acn, line:4, The size property must either be ommited or have the fixed value 20
