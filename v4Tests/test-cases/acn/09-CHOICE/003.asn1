TEST-CASE DEFINITIONS AUTOMATIC TAGS::= BEGIN

	MyPDU ::= SEQUENCE {
        a   ChoiceSelector,
        b   ChoiceType
    }
    
    ChoiceSelector ::= ENUMERATED {
        int1, int2, enm, buf, gg
    }
    
    
    ChoiceType ::= CHOICE {
		int1	INTEGER(0..15),
		int2	INTEGER(0..65535),
		enm		ENUMERATED {
					one(1), two(2), three(3),
					 four(4), thousand(1000)
				},
		buf	 OCTET STRING (SIZE(10)),
		gg  SEQUENCE {
			int1	INTEGER(0..15),
			int2	INTEGER(0..65535),
			enm	ENUMERATED {
					pone(1), ptwo(2), pthree(3),
					 pfour(4), pthousand(1000)
				},
			buf	[APPLICATION 104]	OCTET STRING (SIZE(10))
		}
	}
	
	--pdu1 MyPDU ::= {a gg, b gg : {int1 10, int2 200, enm pone, buf '00112233445566778899'H }}

END

--TCLS     MyPDU[]  ChoiceSelector[]  ChoiceType[]
--TCLS     MyPDU[] {a[], b[]}   ChoiceSelector[]  ChoiceType[]

--TCFC     MyPDU[] {a[], b<a>[]}   ChoiceSelector[]  ChoiceType<ChoiceSelector:sel>[determinant sel] $$$ Asn.1 compiler error is: File:sample1.asn1, line:4, ASN.1 fields cannot act as encoding determinants. Remove field 'a' from the ASN.1 grammar and introduce it in the ACN grammar

--TCLS     MyPDU[] {a[], inserted ChoiceSelector[], b<inserted>[]}   ChoiceSelector[]  ChoiceType<ChoiceSelector:sel>[determinant sel]
