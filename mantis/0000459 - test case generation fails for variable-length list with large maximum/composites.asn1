--
--   Copyright (c) 2015 European Space Agency
--    All Rights Reserved
--
--    Project:    SOIS Electronic Data Sheets
--
--    Module:     composites.asn1
--
--    Author:     SOIS EDS Tooling  (internal unreleased version)
--
--


Composites DEFINITIONS AUTOMATIC TAGS ::= BEGIN


Composites-Long ::= INTEGER (-9223372036854775808..9223372036854775807)

Composites-Byte ::= INTEGER (0..255)


Composites-VarPacket1 ::= SEQUENCE
{
  list SEQUENCE SIZE(0..2000000) OF Composites-Byte
}






END
