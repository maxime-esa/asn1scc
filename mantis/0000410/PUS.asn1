TEST-CASE DEFINITIONS AUTOMATIC TAGS ::= BEGIN

	
	TC-HEADER-SEQUENCE-FLAGS ::= ENUMERATED {
		first-packet,
		continuation-packet,
		last-packet,
		stand-alone-packet
	}
	
	
	SERVICE-TYPE				::=	INTEGER (0..255)
	SERVICE-SUBTYPE				::= INTEGER (0..255)
	
	TM-PACKET ::= SEQUENCE {
		header 	TM-HEADER,
		data	TM-DATA OPTIONAL
	}
	
	TM-HEADER ::= SEQUENCE {
		applicationProcessID	INTEGER(0..2047),
		grouping-flags			TC-HEADER-SEQUENCE-FLAGS,
		sequence-count			INTEGER(0..16383)
	}
	
	TM-DATA ::= SEQUENCE {
		header			TM-DATA-HEADER ,
		sourceData		TM-DATA-SRC	   
	}
	
	TM-DATA-HEADER ::= SEQUENCE {
		packetSubcounter			INTEGER (0..255),
		destinationID				INTEGER (0..7),
		absTime						INTEGER (0..MAX)
	}
	
	TM-DATA-SRC ::= CHOICE {
		tcVerification				TC-VERIFICATION-SERVICE,
		deviceCommandDistribution	DEVICE-COMMAND-DISTTIBUTION
	}
	
	TC-VERIFICATION-SERVICE ::= CHOICE {
		tcAcceptanceReport				TC-ACCEPTANCE-REPORT,
		tcAcceptanceReportFailure		TC-ACCEPTANCE-REPORT-FAILURE,
		tcExecutionStarted				TC-EXECUTION-STARTED,
		tcExecutionProgress				TC-EXECUTION-PROGRESS,
		tcExecutionComplete				TC-EXECUTION-COMPLETE
	}
	
	DEVICE-COMMAND-DISTTIBUTION ::= CHOICE {
		distributingOn-OffCommands			DISTRIBUTING-ON-OFF-COMMANDS,
		distributingRegisterLoadCommands	DISTRIBUTING-REGISTER-LOAD-COMMANDS,
		distributingCPDUCommands			DISTRIBUTING-CPDU-COMMANDS
	}
	
	DUMMY-PACKET ::= INTEGER (0..255)
	
	TC-ACCEPTANCE-REPORT 					::= DUMMY-PACKET
	TC-ACCEPTANCE-REPORT-FAILURE			::= DUMMY-PACKET
	TC-EXECUTION-STARTED					::= DUMMY-PACKET
	TC-EXECUTION-PROGRESS					::= DUMMY-PACKET
	TC-EXECUTION-COMPLETE					::= DUMMY-PACKET
	
	DISTRIBUTING-ON-OFF-COMMANDS			::= DUMMY-PACKET
	DISTRIBUTING-REGISTER-LOAD-COMMANDS     ::= DUMMY-PACKET
	DISTRIBUTING-CPDU-COMMANDS              ::= DUMMY-PACKET
	
END
