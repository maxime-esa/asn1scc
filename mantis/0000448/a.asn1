MY-MOD DEFINITIONS AUTOMATIC TAGS ::= BEGIN


x REAL ::= PLUS-INFINITY

y REAL ::= MINUS-INFINITY

pi REAL ::= 3.1415

minus-e REAL ::= -2.71828

MY-TYPE ::= REAL (MINUS-INFINITY .. PLUS-INFINITY)




END
