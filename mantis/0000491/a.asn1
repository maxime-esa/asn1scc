TASTE-Dataview DEFINITIONS ::=
BEGIN
 LENG-DET ::= INTEGER (1..32)
 WORD ::= INTEGER (0..65535)


 Milbus ::= SEQUENCE {
     words32 SEQUENCE (SIZE(1..32)) OF WORD
 }
 
 
 INT-POS-CS  		::= INTEGER (1..32)
 INT-POS-CS8 		::= INTEGER (1..32)
 INT-POS-CS-BE-16 	::= INTEGER (1..32)
 INT-POS-CS-BE-32 	::= INTEGER (1..32)
 INT-POS-CS-BE-64 	::= INTEGER (1..32)
 INT-POS-CS-LE-16 	::= INTEGER (1..32)
 INT-POS-CS-LE-32 	::= INTEGER (1..32)
 INT-POS-CS-LE-64 	::= INTEGER (1..32)
 
 INT-TWC-CS  		::= INTEGER (1..32)
 INT-TWC-CS8 		::= INTEGER (1..32)
 INT-TWC-CS-BE-16 	::= INTEGER (1..32)
 INT-TWC-CS-BE-32 	::= INTEGER (1..32)
 INT-TWC-CS-BE-64 	::= INTEGER (1..32)
 INT-TWC-CS-LE-16 	::= INTEGER (1..32)
 INT-TWC-CS-LE-32 	::= INTEGER (1..32)
 INT-TWC-CS-LE-64 	::= INTEGER (1..32)

 INT-ASC-CS         ::= INTEGER (1..32)
 INT-BCD-CS         ::= INTEGER (1..32)
 INT-BCD-VS         ::= INTEGER (1..32)
     

END
