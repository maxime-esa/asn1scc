----------------------------------------------------------------------------------------
-- Second module
----------------------------------------------------------------------------------------

SecondModule-Dataview DEFINITIONS ::=
BEGIN

T-SecondModule-Type1                ::= INTEGER

END
