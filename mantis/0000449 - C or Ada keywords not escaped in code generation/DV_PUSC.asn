TC-GENERIC DEFINITIONS ::=  -- Data types shared by several services
BEGIN

Hydra-asa00ar ::= ENUMERATED {
	default(0),
	constant(1)
}

Hydra2 ::= Hydra-asa00ar (constant)

MyStruct ::= SEQUENCE {
	register INTEGER (1..10),
	const2 INTEGER (1..20)
}


END
